(defun c:CreateCircles ()
  (setq diameter 16.0) ; Set the diameter of the circles
  (setq radius (/ diameter 2.0)) ; Calculate the radius

  ; List of points where circles will be created
  (setq points
    '(
      
(20042.41 1706.21)
(20177.91 1706.21)
(21045.50 335.00)
(20042.41 1394.71)
(20042.41 1750.21)
(20177.91 1750.21)
(20177.91 1394.71)
(21185.00 335.00)
(21045.50 705.93)
(21185.00 705.93)
(21046.61 1663.73)
(21185.00 995.43)
(21045.50 45.50)
(21185.00 45.50)
(21045.50 995.43)
(19182.79 746.29)
(20047.50 403.00)
(20183.00 403.00)
(19047.29 746.29)
(19045.78 1750.21)
(19045.78 1706.21)
(19181.28 1706.21)
(20183.00 47.50)
(20177.91 1059.79)
(20177.91 704.29)
(20042.41 704.29)
(20042.41 1059.79)
(20047.50 47.50)
(20047.50 359.00)
(20183.00 359.00)
(22041.80 1374.23)
(22181.30 1374.23)
(22041.80 1623.73)
(22181.30 1663.73)
(22041.80 705.93)
(22181.30 705.93)
(22041.80 1663.73)
(22181.30 1623.73)
(23045.50 995.43)
(23185.00 995.43)
(23045.50 705.93)
(23185.00 45.50)
(23045.50 335.00)
(23185.00 335.00)
(23045.50 45.50)
(21185.00 745.93)
(21046.61 1623.73)
(21186.11 1623.73)
(21045.50 745.93)
(21186.11 1663.73)
(21046.61 1374.23)
(21186.11 1374.23)
(22045.50 335.00)
(22185.00 295.00)
(22041.80 995.43)
(22181.30 995.43)
(22045.50 295.00)
(22185.00 335.00)
(22045.50 45.50)
(22185.00 45.50)
(19181.28 1750.21)
(16047.06 1783.71)
(16177.08 1783.71)
(16042.47 748.29)
(16112.12 1394.71)
(16179.87 1394.71)
(16044.37 1394.71)
(16112.12 1830.21)
(16177.97 748.29)
(17043.50 704.29)
(17179.00 704.29)
(17179.00 1139.79)
(17047.50 483.00)
(17047.50 47.50)
(17183.00 47.50)
(17183.00 483.00)
(16115.25 47.50)
(16050.19 436.50)
(16180.21 436.50)
(16115.25 483.00)
(16183.00 483.00)
(16183.00 47.50)
(16047.50 47.50)
(16042.47 1139.79)
(16110.22 704.29)
(16044.37 1830.21)
(16179.87 1830.21)
(16110.22 1139.79)
(16177.97 1139.79)
(16177.97 704.29)
(16042.47 704.29)
(19183.00 47.50)
(19183.00 403.00)
(19047.50 403.00)
(19047.50 47.50)
(18047.50 89.50)
(18253.00 89.50)
(18150.25 89.50)
(19047.50 359.00)
(19047.29 1059.79)
(19045.78 1394.71)
(19181.28 1394.71)
(19182.79 1059.79)
(19183.00 359.00)
(19047.29 704.29)
(19182.79 704.29)
(17042.30 1830.21)
(17047.50 439.00)
(17183.00 439.00)
(17177.80 1830.21)
(17043.50 1139.79)
(17042.30 1394.71)
(17177.80 1394.71)
(18047.50 47.50)
(18050.00 434.00)
(18150.25 434.00)
(18250.50 434.00)
(18150.25 480.50)
(18253.00 47.50)
(18050.00 480.50)
(18250.50 480.50)
(30297.00 403.00)
(30159.50 45.50)
(30299.00 45.50)
(30161.50 403.00)
(29159.50 1526.47)
(29159.50 678.44)
(29299.00 678.44)
(30161.50 363.00)
(30299.00 625.86)
(30161.50 1613.90)
(30297.00 1613.90)
(30159.50 625.86)
(30297.00 363.00)
(30161.50 983.36)
(30297.00 983.36)
(29299.00 297.00)
(29159.50 297.00)
(29159.50 929.94)
(29159.50 45.50)
(29159.50 335.00)
(29299.00 335.00)
(29299.00 45.50)
(29299.00 929.94)
(29299.00 1274.97)
(29159.50 1274.97)
(29299.00 1526.47)
(29299.00 1564.47)
(29299.00 640.44)
(29159.50 640.44)
(29159.50 1564.47)
(32045.50 1671.91)
(32185.00 1631.91)
(32045.50 1631.91)
(32185.00 1671.91)
(32045.50 1059.55)
(32045.50 1312.41)
(32185.00 1312.41)
(32185.00 740.05)
(33045.50 485.00)
(33115.25 45.50)
(33115.25 485.00)
(33185.00 485.00)
(32045.50 740.05)
(33045.50 45.50)
(33185.00 45.50)
(30159.50 663.86)
(30299.00 663.86)
(32045.50 45.50)
(30297.00 1573.90)
(30159.50 1256.40)
(30299.00 1256.40)
(30161.50 1573.90)
(32185.00 45.50)
(32045.50 700.05)
(32185.00 700.05)
(32185.00 1059.55)
(32045.50 365.00)
(32185.00 405.00)
(32045.50 405.00)
(32185.00 365.00)
(30810.00 215.00)
(24183.00 773.50)
(24183.00 593.50)
(24183.00 411.50)
(24047.50 773.50)
(24047.50 227.50)
(24047.50 411.50)
(24047.50 593.50)
(24183.00 227.50)
(25115.25 953.00)
(25047.50 953.00)
(25047.50 91.50)
(25183.00 953.00)
(25047.50 47.50)
(25183.00 47.50)
(25115.25 47.50)
(23184.13 1374.23)
(23045.50 745.93)
(23185.00 745.93)
(23044.63 1374.23)
(23185.00 705.93)
(23044.63 1663.73)
(23184.13 1663.73)
(24047.50 953.00)
(24183.00 909.00)
(24047.50 91.50)
(24183.00 91.50)
(24047.50 909.00)
(24183.00 953.00)
(24047.50 47.50)
(24183.00 47.50)
(27187.00 257.00)
(27043.50 257.00)
(28045.50 255.00)
(27187.00 43.50)
(26183.00 553.00)
(26047.50 553.00)
(27043.50 43.50)
(28185.00 255.00)
(30810.00 45.50)
(30670.50 45.50)
(30670.50 215.00)
(30810.00 255.00)
(28185.00 45.50)
(28045.50 45.50)
(30670.50 255.00)
(25115.25 909.00)
(25047.50 227.50)
(25047.50 411.50)
(25183.00 909.00)
(25183.00 91.50)
(25115.25 91.50)
(25047.50 909.00)
(25047.50 593.50)
(25183.00 227.50)
(26047.50 47.50)
(26183.00 47.50)
(25183.00 411.50)
(25047.50 773.50)
(25183.00 773.50)
(25183.00 593.50)
(6183.00 1749.35)
(6047.50 1749.35)
(6047.50 361.00)
(6183.00 1393.85)
(6183.00 1046.56)
(6047.50 1046.56)
(6047.50 1393.85)
(6183.00 361.00)
(7044.91 691.06)
(7180.41 691.06)
(7180.41 1126.56)
(7047.50 483.00)
(7047.50 47.50)
(7183.00 47.50)
(7183.00 483.00)
(5130.59 1387.26)
(4995.09 1700.76)
(5130.59 1700.76)
(4995.09 1387.26)
(5130.59 716.26)
(4995.09 1742.76)
(5130.59 1742.76)
(4995.09 358.76)
(6047.50 403.00)
(6047.50 691.06)
(6183.00 691.06)
(6183.00 403.00)
(5130.59 358.76)
(6047.50 47.50)
(6183.00 47.50)
(8183.00 1126.56)
(8047.50 691.06)
(8183.00 691.06)
(8047.50 1126.56)
(8183.00 47.50)
(8047.50 439.00)
(8183.00 439.00)
(8047.50 1829.35)
(8183.00 1785.35)
(8047.50 733.06)
(8183.00 733.06)
(8047.50 1785.35)
(8183.00 1829.35)
(8047.50 1393.85)
(8183.00 1393.85)
(7042.64 1829.35)
(7047.50 439.00)
(7183.00 439.00)
(7178.14 1829.35)
(7044.91 1126.56)
(7042.64 1393.85)
(7178.14 1393.85)
(7115.25 439.00)
(8047.50 483.00)
(8183.00 483.00)
(8047.50 47.50)
(7178.14 1787.35)
(7044.91 733.06)
(7180.41 733.06)
(7042.64 1787.35)
(4995.09 716.26)
(3183.00 483.00)
(3047.50 483.00)
(3183.00 439.00)
(3183.00 47.50)
(2045.50 555.50)
(2185.00 555.50)
(3047.50 47.50)
(3047.50 439.00)
(3047.50 1389.50)
(3183.00 1389.50)
(3183.00 1825.00)
(3047.50 1154.00)
(3047.50 718.50)
(3183.00 718.50)
(3183.00 1154.00)
(2045.50 1282.00)
(2185.00 1282.00)
(2185.00 992.50)
(2045.50 45.50)
(2045.50 335.00)
(2185.00 335.00)
(2185.00 45.50)
(2045.50 992.50)
(2185.00 805.00)
(2185.00 515.50)
(2045.50 515.50)
(2045.50 805.00)
(2045.50 295.00)
(2185.00 295.00)
(2115.00 295.00)
(4183.00 359.00)
(4047.50 758.50)
(4183.00 758.50)
(4115.25 359.00)
(4047.50 1389.50)
(4183.00 1389.50)
(4047.50 359.00)
(4047.50 1703.00)
(5130.59 45.26)
(4995.09 1071.76)
(5130.59 1071.76)
(4995.09 45.26)
(4183.00 1703.00)
(4995.09 400.76)
(5130.59 400.76)
(3047.50 762.50)
(4047.50 403.00)
(4183.00 403.00)
(3183.00 762.50)
(3047.50 1825.00)
(3183.00 1781.00)
(3047.50 1781.00)
(4047.50 47.50)
(4183.00 718.50)
(4047.50 1745.00)
(4183.00 1745.00)
(4047.50 718.50)
(4183.00 47.50)
(4047.50 1074.00)
(4183.00 1074.00)
(13047.50 1127.42)
(13183.00 1127.42)
(13183.00 691.92)
(13047.50 47.50)
(13047.50 483.00)
(13183.00 483.00)
(13183.00 47.50)
(13047.50 691.92)
(13183.16 1394.71)
(13047.66 1394.71)
(13047.66 1786.21)
(13183.16 1830.21)
(13047.50 1083.42)
(13183.00 1083.42)
(13047.66 1830.21)
(12183.00 359.00)
(12044.91 1047.42)
(12180.41 1047.42)
(12047.50 359.00)
(12183.00 403.00)
(12183.00 47.50)
(12047.50 47.50)
(12180.41 691.92)
(12044.91 1394.71)
(12044.91 1706.21)
(12180.41 1706.21)
(12180.41 1394.71)
(12044.91 691.92)
(12044.91 1750.21)
(12180.41 1750.21)
(14183.16 1788.21)
(14047.66 1788.21)
(15050.00 550.50)
(14183.00 89.50)
(14183.16 1394.71)
(14047.66 1394.71)
(14047.50 89.50)
(15250.50 550.50)
(15050.00 96.50)
(15250.50 96.50)
(16047.50 483.00)
(15250.50 501.50)
(15250.50 50.00)
(15050.00 50.00)
(15050.00 501.50)
(14183.00 483.00)
(14183.00 47.50)
(14047.50 47.50)
(14047.50 483.00)
(13183.16 1786.21)
(13047.50 89.50)
(13183.00 89.50)
(14047.50 1127.42)
(14183.00 1083.42)
(14047.66 1830.21)
(14183.16 1830.21)
(14047.50 1083.42)
(14183.00 1127.42)
(14183.00 691.92)
(14047.50 691.92)
(12047.50 403.00)
(9255.53 1126.56)
(9152.78 1126.56)
(9255.53 691.06)
(9050.03 1126.56)
(9042.44 1785.35)
(9145.19 1785.35)
(9247.94 1785.35)
(9152.78 691.06)
(10047.50 483.00)
(10183.00 483.00)
(10047.50 47.50)
(9255.53 735.06)
(9050.03 691.06)
(9050.03 735.06)
(9152.78 735.06)
(9150.25 47.50)
(9047.50 47.50)
(9047.50 439.00)
(9253.00 47.50)
(9047.50 483.00)
(9253.00 483.00)
(9150.25 483.00)
(9150.25 439.00)
(9247.94 1393.85)
(9145.19 1393.85)
(9042.44 1393.85)
(9145.19 1829.35)
(9253.00 439.00)
(9042.44 1829.35)
(9247.94 1829.35)
(11183.00 47.50)
(11047.50 1047.42)
(11183.00 1047.42)
(11047.50 47.50)
(10181.63 733.06)
(11047.50 403.00)
(11183.00 403.00)
(11047.50 691.92)
(11183.00 1394.71)
(11047.50 1706.21)
(11183.00 1706.21)
(11047.50 1394.71)
(11183.00 691.92)
(11047.50 1750.21)
(11183.00 1750.21)
(10179.80 1829.35)
(10044.30 1393.85)
(10179.80 1393.85)
(10044.30 1829.35)
(10183.00 47.50)
(10047.50 439.00)
(10183.00 439.00)
(10044.30 1785.35)
(10181.63 691.06)
(10046.13 733.06)
(10113.88 733.06)
(10046.13 691.06)
(10179.80 1785.35)
(10046.13 1126.56)
(10181.63 1126.56)

    )
  )

  ; Iterate through the list of points and create a circle at each point
  (foreach pt points
    (command "CIRCLE" pt radius)
  )
  
  (princ)
)
